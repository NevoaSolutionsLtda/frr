// SPDX-License-Identifier: BSD-2-Clause
submodule frr-bgp-common-multiprotocol {
  yang-version 1.1;

  belongs-to frr-bgp {
    prefix "bgp";
  }

  import frr-routing {
    prefix frr-rt;
  }

  import ietf-inet-types {
    prefix inet;
  }

  import ietf-yang-types {
    prefix yang;
  }

  organization
    "FRRouting";
  contact
    "FRR Users List: <mailto:frog@lists.frrouting.org> FRR Development
     List: <mailto:dev@lists.frrouting.org>";
  description
    "This module contains general data definitions for use in BGP
     Multiprotocol.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2019-12-03 {
    description
      "Initial revision.";
  }

  grouping mp-afi-safi-config {
    description
      "Configuration parameters used for all BGP AFI-SAFIs.";
    leaf afi-safi-name {
      type identityref {
        base frr-rt:afi-safi-type;
      }
      description
        "AFI, SAFI.";
    }
  }

  grouping mp-all-afi-safi-list-contents {
    description
      "A common grouping used for contents of the list that is used
       for AFI-SAFI entries.";
    container ipv4-unicast {
      when "derived-from-or-self(../afi-safi-name, 'frr-rt:ipv4-unicast')" {
        description
          "Include this container for IPv4 Unicast specific
           configuration.";
      }
      description
        "IPv4 unicast configuration options.";
    }

    container ipv6-unicast {
      when "derived-from-or-self(../afi-safi-name, 'frr-rt:ipv6-unicast')" {
        description
          "Include this container for IPv6 Unicast specific
           configuration.";
      }
      description
        "IPv6 unicast configuration options.";
    }

    container ipv4-labeled-unicast {
      when "derived-from-or-self(../afi-safi-name, 'frr-rt:ipv4-labeled-unicast')" {
        description
          "Include this container for IPv4 Labeled Unicast specific
           configuration.";
      }
      description
        "IPv4 Labeled Unicast configuration options.";
    }

    container ipv6-labeled-unicast {
      when "derived-from-or-self(../afi-safi-name, 'frr-rt:ipv6-labeled-unicast')" {
        description
          "Include this container for IPv6 Labeled Unicast specific
           configuration.";
      }
      description
        "IPv6 Labeled Unicast configuration options.";
    }

    container l3vpn-ipv4-unicast {
      when "derived-from-or-self(../afi-safi-name, 'frr-rt:l3vpn-ipv4-unicast')" {
        description
          "Include this container for IPv4 Unicast L3VPN specific
           configuration.";
      }
      description
        "Unicast IPv4 L3VPN configuration options.";
    }

    container l3vpn-ipv6-unicast {
      when "derived-from-or-self(../afi-safi-name, 'frr-rt:l3vpn-ipv6-unicast')" {
        description
          "Include this container for unicast IPv6 L3VPN specific
           configuration.";
      }
      description
        "Unicast IPv6 L3VPN configuration options.";
    }

    container l3vpn-ipv4-multicast {
      when "derived-from-or-self(../afi-safi-name, 'frr-rt:l3vpn-ipv4-multicast')" {
        description
          "Include this container for multicast IPv4 L3VPN specific
           configuration.";
      }
      description
        "Multicast IPv4 L3VPN configuration options.";
    }

    container l3vpn-ipv6-multicast {
      when "derived-from-or-self(../afi-safi-name, 'frr-rt:l3vpn-ipv6-multicast')" {
        description
          "Include this container for multicast IPv6 L3VPN specific
           configuration.";
      }
      description
        "Multicast IPv6 L3VPN configuration options.";
    }

    container l2vpn-vpls {
      when "derived-from-or-self(../afi-safi-name, 'frr-rt:l2vpn-vpls')" {
        description
          "Include this container for BGP-signalled VPLS specific
           configuration.";
      }
      description
        "BGP-signalled VPLS configuration options.";
    }

    container l2vpn-evpn {
      when "derived-from-or-self(../afi-safi-name, 'frr-rt:l2vpn-evpn')" {
        description
          "Include this container for BGP EVPN specific
           configuration.";
      }
      description
        "BGP EVPN configuration options.";

      leaf advertise-all-vni {
        type boolean;
        default "false";
        description
          "Advertise all locally-configured VNIs as EVPN type-3 routes.";
      }

      leaf advertise-svi-ip {
        type boolean;
        default "false";
        description
          "Advertise SVI IP addresses as EVPN type-2 routes.";
      }

      leaf advertise-default-gw {
        type boolean;
        default "false";
        description
          "Advertise default-gateway extended community on EVPN type-2 routes.";
      }

      leaf advertise-subnet {
        type boolean;
        default "false";
        description
          "Advertise locally-configured subnets as EVPN type-5 routes.";
      }

      leaf autort-rfc8365-compatible {
        type boolean;
        default "false";
        description
          "Generate auto-RTs that are RFC 8365 compatible.";
      }

      leaf use-es-l3nhg {
        type boolean;
        default "false";
        description
          "Use EVPN Ethernet Segment L3 next-hop-group for ECMP forwarding.";
      }

      leaf enable-resolve-overlay-index {
        type boolean;
        default "false";
        description
          "Enable resolving overlay-index for EVPN routes.";
      }

      leaf disable-ead-evi-rx {
        type boolean;
        default "false";
        description
          "Disable the receipt of EAD-per-EVI EVPN type-1 routes.";
      }

      leaf disable-ead-evi-tx {
        type boolean;
        default "false";
        description
          "Disable the generation of EAD-per-EVI EVPN type-1 routes.";
      }

      container advertise-pip {
        presence
          "Advertise Primary IP for EVPN routes (split between primary and
           system IP).";
        description
          "Advertise-pip parameters: when present, BGP advertises the
           primary IP address (and optionally MAC) in EVPN type-2 routes.";

        leaf ip {
          type inet:ipv4-address;
          description "Primary IPv4 address to advertise.";
        }

        leaf mac {
          type yang:mac-address;
          description "Primary MAC to advertise.";
        }
      }

      container advertise {
        description
          "Advertise selected routes from other address-families into EVPN.
           One sub-container per AFI to advertise.";

        leaf ipv4-unicast {
          type boolean;
          default "false";
          description
            "Advertise IPv4-unicast routes into EVPN as type-5 prefix
             routes.";
        }

        leaf ipv4-unicast-route-map {
          when "../ipv4-unicast = 'true'";
          type string;
          description
            "Route-map filter applied to IPv4-unicast -> EVPN advertisement.";
        }

        leaf ipv6-unicast {
          type boolean;
          default "false";
          description
            "Advertise IPv6-unicast routes into EVPN as type-5 prefix
             routes.";
        }

        leaf ipv6-unicast-route-map {
          when "../ipv6-unicast = 'true'";
          type string;
          description
            "Route-map filter applied to IPv6-unicast -> EVPN advertisement.";
        }
      }

      container dup-addr-detection {
        description
          "EVPN MAC mobility / duplicate-address-detection parameters.";

        leaf max-moves {
          type uint16 { range "2..1000"; }
          default "5";
          description "Maximum moves before the MAC is flagged duplicate.";
        }

        leaf time {
          type uint16 { range "2..1800"; }
          units "seconds";
          default "180";
          description
            "Detection window in which max-moves is counted.";
        }

        choice freeze-action {
          description
            "Action when a duplicate MAC is detected.";

          case permanent-case {
            leaf freeze-permanent {
              type boolean;
              description
                "When 'true', freeze the duplicate MAC permanently.";
            }
          }

          case timed-case {
            leaf freeze-time {
              type uint16 { range "30..3600"; }
              units "seconds";
              description
                "Freeze duration before the MAC is unfrozen.";
            }
          }
        }
      }

      leaf flooding {
        type enumeration {
          enum "disable"              { value 0; }
          enum "head-end-replication" { value 1; }
        }
        default "head-end-replication";
        description
          "BUM (broadcast/unknown-unicast/multicast) flooding strategy
           for the EVPN VNIs in this instance.";
      }

      leaf mac-vrf-soo {
        type string {
          length "3..64";
        }
        description
          "MAC-VRF Site-of-Origin extended community (RT format).";
      }

      container ead-es {
        description
          "EAD-per-ES (Ethernet Segment) parameters.";

        container fragmentation {
          description
            "EAD-per-ES fragmentation control.";

          leaf evi-limit {
            type uint16 { range "1..1000"; }
            default "128";
            description
              "Maximum number of EVI labels per EAD-per-ES route fragment.";
          }
        }

        leaf-list route-target-export {
          type string {
            length "3..64";
          }
          description
            "Route-target(s) attached to EAD-per-ES routes on export.";
        }
      }
    }

    container ipv4-multicast {
      when "derived-from-or-self(../afi-safi-name, 'frr-rt:ipv4-multicast')" {
        description
          "Include this container for IPv4 multicast specific
           configuration.";
      }
      description
        "IPv4 multicast configuration options.";
    }

    container ipv6-multicast {
      when "derived-from-or-self(../afi-safi-name, 'frr-rt:ipv6-multicast')" {
        description
          "Include this container for IPv6 multicast specific
           configuration.";
      }
      description
        "IPv6 multicast configuration options.";
    }

    container ipv4-flowspec {
      when "derived-from-or-self(../afi-safi-name, 'frr-rt:ipv4-flowspec')" {
        description
          "Include this container for IPv4 flowspec specific
           configuration.";
      }
      description
        "IPv4 flowspec configuration options.";

      leaf-list local-install-interface {
        type string {
          length "1..63";
        }
        description
          "Interface(s) on which flowspec rules are locally installed
           (corresponds to `local-install INTERFACE` in the IPv4
           flowspec address-family CLI).";
      }
    }

    container ipv6-flowspec {
      when "derived-from-or-self(../afi-safi-name, 'frr-rt:ipv6-flowspec')" {
        description
          "Include this container for IPv6 flowspec specific
           configuration.";
      }
      description
        "IPv6 flowspec configuration options.";

      leaf-list local-install-interface {
        type string {
          length "1..63";
        }
        description
          "Interface(s) on which flowspec rules are locally installed.";
      }
    }
  }
}
