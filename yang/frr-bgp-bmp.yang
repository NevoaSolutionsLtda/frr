// SPDX-License-Identifier: BSD-2-Clause
submodule frr-bgp-bmp {
  yang-version 1.1;

  belongs-to frr-bgp {
    prefix "bgp";
  }

  import ietf-inet-types {
    prefix inet;
  }

  import frr-bgp-types {
    prefix frr-bt;
  }
  organization
    "FRRouting";
  contact
    "FRR Users List: <mailto:frog@lists.frrouting.org> FRR Development
     List: <mailto:dev@lists.frrouting.org>";
  description
    "This submodule defines a model for managing FRR BGP BMP.

     Copyright 2020 FRRouting

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2026-07-21 {
    description
      "Add BMP import-vrf and experimental stats knobs to match CLI.
       Default stats-send-experimental to true to match classic.
       Constrain max-retry-time >= min-retry-time via YANG must.
       Add source-interface on outbound sessions and loc-rib monitor.";
    reference
      "FRRouting.";
  }

  revision 2019-12-03 {
    description
      "Initial revision.";
    reference
      "FRRouting.";
  }

  grouping bmp-incoming-session {
    description
      "Grouping for BMP incoming session configuration.";
    container incoming-session {
      description
        "Configuration for BMP incoming (listening) sessions.";
      list session-list {
        key "address tcp-port";
        description
          "List of BMP incoming session entries.";
        leaf address {
          type inet:ip-address;
          description
            "IPv4 address to listen on.";
        }

        leaf tcp-port {
          type uint32;
          description
            "TCP port to listen on for BMP incoming sessions.";
        }
      }
    }
  }

  grouping bmp-outgoing-session {
    description
      "Grouping for BMP outgoing session configuration.";
    container outgoing-session {
      description
        "Configuration for BMP outgoing (connecting) sessions.";
      list session-list {
        key "hostname tcp-port";
        description
          "List of BMP outgoing session entries.";
        leaf hostname {
          type string;
          description
            "Hostname or IP address of the remote BMP monitoring station.";
        }

        leaf tcp-port {
          type uint32;
          description
            "TCP port to connect to for BMP outgoing sessions.";
        }

        leaf min-retry-time {
          type uint32 {
            range "100..86400000";
          }
          units "milliseconds";
          default "30000";
          description
            "Minimum connection retry interval.";
        }

        leaf max-retry-time {
          type uint32 {
            range "100..86400000";
          }
          units "milliseconds";
          default "720000";
          must ". >= ../min-retry-time" {
            error-message
              "BMP max-retry-time must be greater than or equal to min-retry-time.";
          }
          description
            "Maximum connection retry interval.";
        }

        leaf source-interface {
          type string;
          description
            "Source interface for the outbound BMP connection.
             Maps to: bmp connect ... source-interface IFNAME.";
        }
      }
    }
  }

  grouping bmp-afi-safis {
    description
      "Grouping for BMP AFI-SAFI configuration.";
    container afi-safis {
      description
        "List of address-families associated with the BGP
         instance.";
      list afi-safi {
        key "afi-safi-name";
        description
          "AFI, SAFI configuration available for the
           neighbour or group.";
        uses mp-afi-safi-config;

        uses mp-all-afi-safi-list-contents;
      }
    }
  }

  grouping bmp-afi-safi-common-config {
    description
      "Grouping for common BMP AFI-SAFI configuration parameters.";
    container common-config {
      description
        "Common configuration for BMP AFI-SAFI entries.";
      leaf pre-policy {
        type boolean;
        default "false";
        description
          "Send state before policy and filter processing.";
      }

      leaf post-policy {
        type boolean;
        default "false";
        description
          "Send state after policy and filter processing.";
      }

      leaf loc-rib {
        type boolean;
        default "false";
        description
          "Send Loc-RIB state after the decision process.
           Maps to: bmp monitor ... loc-rib.";
      }
    }
  }

  grouping global-bmp-config {
    description
      "Structural grouping used to include filter
       configuration for BMP.";
    container bmp-config {
      description
        "BMP related parameters.";
      list target-list {
        key "target-name";
        description
          "List of BMP target groups.";
        leaf target-name {
          type string;
          description
            "Targets group name.";
        }

        uses bmp-incoming-session;

        uses bmp-outgoing-session;

        leaf mirror {
          type boolean;
          default "false";
          description
            "When set to 'TRUE' it send BMP route mirroring messages.";
        }

        leaf stats-time {
          type uint32 {
            range "100..86400000";
          }
          units "milliseconds";
          description
            "Interval to send BMP Stats.";
        }

        leaf ipv4-access-list {
          type frr-bt:access-list-ref;
          description
            "Access list to restrict BMP sessions.";
        }

        leaf ipv6-access-list {
          type frr-bt:access-list-ref;
          description
            "Access list to restrict BMP sessions.";
        }

        leaf-list import-vrf {
          type string;
          description
            "Import BMP monitoring state from the named VRF(s).
             Maps to: bmp import-vrf NAME.";
        }

        leaf stats-send-experimental {
          type boolean;
          default "true";
          description
            "Include experimental BMP statistics TLVs.
             Maps to: bmp stats send-experimental.
             Default true matches classic FRR behaviour for new targets.";
        }

        uses bmp-afi-safis;
      }

      leaf mirror-buffer-limit {
        type uint32 {
          range "0..4294967294";
        }
        units "bytes";
        description
          "Maximum memory used for buffered mirroring messages.";
      }
    }
  }
}
